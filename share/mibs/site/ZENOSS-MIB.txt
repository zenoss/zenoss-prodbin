ZENOSS-MIB DEFINITIONS ::= BEGIN

IMPORTS
    enterprises, OBJECT-TYPE, MODULE-IDENTITY, NOTIFICATION-TYPE, Unsigned32
        FROM SNMPv2-SMI

    DateAndTime, TEXTUAL-CONVENTION         FROM SNMPv2-TC

    MODULE-COMPLIANCE, OBJECT-GROUP, NOTIFICATION-GROUP
        FROM SNMPv2-CONF;

zen OBJECT IDENTIFIER ::= { enterprises 14296 }

zenMIB MODULE-IDENTITY
    LAST-UPDATED    "201306040000Z"
    ORGANIZATION    "Zenoss, Inc."
    CONTACT-INFO    "support@zenoss.com"
    DESCRIPTION
        "Defines structure of traps sent by Zenoss."
    REVISION        "201306040000Z"
    DESCRIPTION
        "Third revision."
    ::= { zen 1 }

zenTrapDef OBJECT IDENTIFIER ::= { zenMIB 100 }

--
-- textual conventions
--

ZenUUID ::= TEXTUAL-CONVENTION
    DISPLAY-HINT "4x-2x-2x-2x-6x"
    STATUS      current
    DESCRIPTION
        "Represents the universally unique identifier (UUID) for a Zenoss
         object. Object examples include events, services, devices and
         components.

         UUIDs as defined by RFC 4122 (http://tools.ietf.org/rfc/rfc4122.txt)"
    SYNTAX      OCTET STRING (SIZE (0|16))

ZenEventStatus ::= TEXTUAL-CONVENTION
    STATUS      current
    DESCRIPTION
        "Represents a Zenoss event status."

    SYNTAX      Unsigned32 {
                    new(0),
                    acknowledged(1),
                    suppressed(2),
                    closed(3),
                    cleared(4),
                    dropped(5),
                    aged(6),
                    other(99)
                }

ZenEventSeverity ::= TEXTUAL-CONVENTION
    STATUS      current
    DESCRIPTION
        "Represents a Zenoss event severity."

    SYNTAX      Unsigned32 {
                    clear(0),
                    debug(1),
                    info(2),
                    warning(3),
                    error(4),
                    critical(5),
                    other(99)
                }

--
-- objects
--

evtId OBJECT-TYPE
    SYNTAX      OCTET STRING (SIZE (0..255))
    MAX-ACCESS  read-only
    STATUS      current
    DESCRIPTION
        "Unique identifier ID of the event."
    ::= { zenTrapDef 1 }

evtDedupid OBJECT-TYPE
    SYNTAX      OCTET STRING (SIZE (0..255))
    MAX-ACCESS  read-only
    STATUS      current
    DESCRIPTION
        "De-duplication ID of the event."
    ::= { zenTrapDef 2 }

evtDevice OBJECT-TYPE
    SYNTAX      OCTET STRING (SIZE (0..255))
    MAX-ACCESS  read-only
    STATUS      current
    DESCRIPTION
        "ID of the Device associated with the event."
    ::= { zenTrapDef 3 }

evtComponent OBJECT-TYPE
    SYNTAX      OCTET STRING (SIZE (0..255))
    MAX-ACCESS  read-only
    STATUS      current
    DESCRIPTION
        "ID of the Device component associated with the event."
    ::= { zenTrapDef 4 }

evtClass OBJECT-TYPE
    SYNTAX      OCTET STRING (SIZE (0..255))
    MAX-ACCESS  read-only
    STATUS      current
    DESCRIPTION
        "Event classification."
    ::= { zenTrapDef 5 }

evtKey OBJECT-TYPE
    SYNTAX      OCTET STRING (SIZE (0..255))
    MAX-ACCESS  read-only
    STATUS      current
    DESCRIPTION
        "Event key used for refining event granularity beyond device and
        component. Used in de-duplication, auto-clearing."
    ::= { zenTrapDef 6 }

evtSummary OBJECT-TYPE
    SYNTAX      OCTET STRING (SIZE (0..255))
    MAX-ACCESS  read-only
    STATUS      current
    DESCRIPTION
        "Event message truncated to 128 characters."
    ::= { zenTrapDef 7 }

evtMessage OBJECT-TYPE
 	SYNTAX      OCTET STRING (SIZE (0..255))
 	MAX-ACCESS  read-only
 	STATUS      current
 	DESCRIPTION
 	    "Event message."
 	::= { zenTrapDef 8 }

evtSeverity OBJECT-TYPE
    SYNTAX      ZenEventSeverity
    MAX-ACCESS  read-only
    STATUS      current
    DESCRIPTION
        "Severity of event. See ZenEventSeverity textual convention for possible values."
    ::= { zenTrapDef 9 }

evtState OBJECT-TYPE
    SYNTAX      ZenEventStatus
    MAX-ACCESS  read-only
    STATUS      current
    DESCRIPTION
        "Status of event. See ZenEventStatus textual convention for possible values."
    ::= { zenTrapDef 10 }

evtClassKey OBJECT-TYPE
    SYNTAX      OCTET STRING (SIZE (0..255))
    MAX-ACCESS  read-only
    STATUS      current
    DESCRIPTION
        "Event class key for rule processing often matches component."
    ::= { zenTrapDef 11 }

evtGroup OBJECT-TYPE
    SYNTAX      OCTET STRING (SIZE (0..255))
    MAX-ACCESS  read-only
    STATUS      current
    DESCRIPTION
        "Logical grouping of event sources."
    ::= { zenTrapDef 12 }

evtStateChange OBJECT-TYPE
    SYNTAX      OCTET STRING (SIZE (0..255))
    MAX-ACCESS  read-only
    STATUS      current
    DESCRIPTION
        "Last time event changed through administrative activity."
    ::= { zenTrapDef 13 }

evtFirstTime OBJECT-TYPE
    SYNTAX      OCTET STRING (SIZE (0..255))
    MAX-ACCESS  read-only
    STATUS      current
    DESCRIPTION
        "First time an event was received."
    ::= { zenTrapDef 14 }

evtLastTime OBJECT-TYPE
    SYNTAX      OCTET STRING (SIZE (0..255))
    MAX-ACCESS  read-only
    STATUS      current
    DESCRIPTION
        "Last time an event was received."
    ::= { zenTrapDef 15 }

evtCount OBJECT-TYPE
    SYNTAX      OCTET STRING (SIZE (0..255))
    MAX-ACCESS  read-only
    STATUS      current
    DESCRIPTION
        "Number of times this event has been seen."
    ::= { zenTrapDef 16 }

evtProdState OBJECT-TYPE
    SYNTAX      OCTET STRING (SIZE (0..255))
    MAX-ACCESS  read-only
    STATUS      current
    DESCRIPTION
        "Production state of the device or component associated with this
        event."
    ::= { zenTrapDef 17 }

evtAgent OBJECT-TYPE
    SYNTAX      OCTET STRING (SIZE (0..255))
    MAX-ACCESS  read-only
    STATUS      current
    DESCRIPTION
        "Collector process that received or created this event."
    ::= { zenTrapDef 20 }

evtDeviceClass OBJECT-TYPE
    SYNTAX      OCTET STRING (SIZE (0..255))
    MAX-ACCESS  read-only
    STATUS      current
    DESCRIPTION
        "Class of device that this event is associated with."
    ::= { zenTrapDef 21 }

evtLocation OBJECT-TYPE
    SYNTAX      OCTET STRING (SIZE (0..255))
    MAX-ACCESS  read-only
    STATUS      current
    DESCRIPTION
        "Location of device that this event is associated with."
    ::= { zenTrapDef 22 }

evtSystems OBJECT-TYPE
    SYNTAX      OCTET STRING (SIZE (0..255))
    MAX-ACCESS  read-only
    STATUS      current
    DESCRIPTION
        "Systems containing the device that this event is associated with."
    ::= { zenTrapDef 23 }

evtDeviceGroups OBJECT-TYPE
    SYNTAX      OCTET STRING (SIZE (0..255))
    MAX-ACCESS  read-only
    STATUS      current
    DESCRIPTION
        "Groups containing the device that this event is associated with."
    ::= { zenTrapDef 24 }

evtIpAddress OBJECT-TYPE
    SYNTAX      OCTET STRING (SIZE (0..255))
    MAX-ACCESS  read-only
    STATUS      current
    DESCRIPTION
        "IP address that this event was generated or sent from."
    ::= { zenTrapDef 25 }

evtFacility OBJECT-TYPE
    SYNTAX      Unsigned32
    MAX-ACCESS  read-only
    STATUS      current
    DESCRIPTION
        "Syslog facility if the event was initially sent as a syslog."
    ::= { zenTrapDef 26 }

evtPriority OBJECT-TYPE
    SYNTAX      Unsigned32
    MAX-ACCESS  read-only
    STATUS      current
    DESCRIPTION
        "Syslog priority if the event was initially sent as a syslog."
    ::= { zenTrapDef 27 }

evtNtEvId OBJECT-TYPE
    SYNTAX      OCTET STRING (SIZE (0..255))
    MAX-ACCESS  read-only
    STATUS      current
    DESCRIPTION
        "Windows NT_EVENT_ID if the event was initially received from Windows
        event log."
    ::= { zenTrapDef 28 }

evtOwnerId OBJECT-TYPE
    SYNTAX      OCTET STRING (SIZE (0..255))
    MAX-ACCESS  read-only
    STATUS      current
    DESCRIPTION
        "User that acknowledged this event."
    ::= { zenTrapDef 29 }

evtClearId OBJECT-TYPE
    SYNTAX      OCTET STRING (SIZE (0..255))
    MAX-ACCESS  read-only
    STATUS      current
    DESCRIPTION
        "evtId that cleared this event."
    ::= { zenTrapDef 31 }

evtDevicePriority OBJECT-TYPE
    SYNTAX      OCTET STRING (SIZE (0..255))
    MAX-ACCESS  read-only
    STATUS      current
    DESCRIPTION
        "Priority of the device that this event is associated with."
    ::= { zenTrapDef 32 }

evtClassMapping OBJECT-TYPE
    SYNTAX      OCTET STRING (SIZE (0..255))
    MAX-ACCESS  read-only
    STATUS      current
    DESCRIPTION
        "Name of the event class mapping that matched this event."
    ::= { zenTrapDef 33 }

evtDeviceName OBJECT-TYPE
    SYNTAX      OCTET STRING (SIZE (0..255))
    MAX-ACCESS  read-only
    STATUS      current
    DESCRIPTION
        "Name of device associated with the event."
    ::= { zenTrapDef 34 }

evtComponentName OBJECT-TYPE
    SYNTAX      OCTET STRING (SIZE (0..255))
    MAX-ACCESS  read-only
    STATUS      current
    DESCRIPTION
        "Name of device component associated with the event."
    ::= { zenTrapDef 35 }


zenNotifications    OBJECT IDENTIFIER ::= { zenTrapDef 0 }
zenTraps            OBJECT IDENTIFIER ::= { zenNotifications 0 }


zenGenTrap NOTIFICATION-TYPE
    OBJECTS {
        evtId,
        evtDedupid,
        evtDevice,
        evtDeviceName,
        evtComponent,
        evtComponentName,
        evtClass,
        evtKey,
        evtSummary,
        evtMessage,
        evtSeverity,
        evtState,
        evtClassKey,
        evtGroup,
        evtStateChange,
        evtFirstTime,
        evtLastTime,
        evtCount,
        evtProdState,
        evtAgent,
        evtDeviceClass,
        evtLocation,
        evtSystems,
        evtDeviceGroups,
        evtIpAddress,
        evtFacility,
        evtPriority,
        evtNtEvId,
        evtOwnerId,
        evtClearId,
        evtDevicePriority,
        evtClassMapping,
        evtDeviceName,
        evtComponentName
    }
    STATUS current
    DESCRIPTION
        "The trap notifying of when an event is received by the Zen server."
    ::= { zenTraps 1 }

--
-- conformance information
--

zenMIBConformance   OBJECT IDENTIFIER ::= { zenMIB 2 }

zenMIBCompliances   OBJECT IDENTIFIER ::= { zenMIBConformance 1 }
zenMIBGroups        OBJECT IDENTIFIER ::= { zenMIBConformance 2 }

-- compliance statements

zenMIBCompliance MODULE-COMPLIANCE
    STATUS current
    DESCRIPTION
        "The compliance statement for SNMPv2 entities which
        implement UDP over IPv6."
    MODULE
        MANDATORY-GROUPS {
            zenMIBObjectGroup,
            zenMIBTrapGroup
        }
   ::= { zenMIBCompliances 1 }

zenMIBObjectGroup OBJECT-GROUP
    OBJECTS {
        evtId,
        evtDedupid,
        evtDevice,
        evtDeviceName,
        evtComponent,
        evtComponentName,
        evtClass,
        evtKey,
        evtSummary,
        evtMessage,
        evtSeverity,
        evtState,
        evtClassKey,
        evtGroup,
        evtStateChange,
        evtFirstTime,
        evtLastTime,
        evtCount,
        evtProdState,
        evtAgent,
        evtDeviceClass,
        evtLocation,
        evtSystems,
        evtDeviceGroups,
        evtIpAddress,
        evtFacility,
        evtPriority,
        evtNtEvId,
        evtOwnerId,
        evtClearId,
        evtDevicePriority,
        evtClassMapping,
        evtDeviceName,
        evtComponentName
    }
    STATUS current
    DESCRIPTION
        "The group of objects providing trap contents."
    ::= { zenMIBGroups 1 }

zenMIBTrapGroup NOTIFICATION-GROUP
    NOTIFICATIONS {
        zenGenTrap
    }
    STATUS current
    DESCRIPTION
        "The group of objects providing traps."
    ::= { zenMIBGroups 2 }

END
